from FreeCAD import Base

#%% Basic sample tab shape
tabL = 17.45
tabW = 11.75
tabH = 0.8
tabPoint = Base.Vector(-tabL/2, -tabW/2, -tabH/2)
tab = Part.makeBox(tabL, tabW, tabH, tabPoint)
tab_center = tab.CenterOfMass
#tab_edgeZ_idx = [0, 2, 4, 6]
#tab_edgeZ = [tab.Edges[i] for i in tab_edgeZ_idx]
#tab_fillet = 0.1
#tab = tab.makeFillet(tab_fillet, tab_edgeZ)

tongueL = 4.40
tongueW = 4.5
tongueH = tabH
tonguePoint = Base.Vector(tabL/2, -tongueW/2, -tongueH/2)
tongue = Part.makeBox(tongueL, tongueW, tongueH, tonguePoint)
tongue_center = tongue.CenterOfMass

# Tongue edges correct
#tongue_edgeZ_idx = [4, 6]
#tongue_edgeZ = [tongue.Edges[i] for i in tongue_edgeZ_idx]
#tongue_fillet = tab_fillet
#tongue = tongue.makeFillet(tongue_fillet, tongue_edgeZ)

depression_tabL = 5.00
depression_tabW = 3.50
depression_tabH = 0.50
depressionPoint = Base.Vector(-tabL/2+depression_tabL/2, -depression_tabW/2,
								tabH/2-depression_tabH)

depression_tab = Part.makeBox(depression_tabL, depression_tabW,
								depression_tabH, depressionPoint)
depression_center = depression_tab.CenterOfMass
# Depression edges correct.
#depression_edgeZ_idx = [0, 2, 4, 6]
#depression_edgeZ = [depression_tab.Edges[i] 
#					for i in depression_edgeZ_idx]
#depression_tab_fillet = 0.1
#depression_tab = depression_tab.makeFillet(depression_tab_fillet,
#											depression_edgeZ)


depression_tongueL = 2.75
depression_tongueW = 2.75
depression_tongueH = depression_tabH

depression_tonguePoint = Base.Vector(-tabL/2+depression_tabL/2+depression_tabL,
							-depression_tongueW/2,
							tabH/2-depression_tongueH)
depression_tongue = Part.makeBox(depression_tongueL, depression_tongueW,
								depression_tongueH,
								depression_tonguePoint)

# Depression tongue edges correct
#depression_tongue_edgeZ_idx = [4,6]
#depression_tongue_edgeZ = [depression_tongue.Edges[i]
#							for i in depression_tongue_edgeZ_idx]
#depression_tongue_fillet = depression_tab_fillet
#depression_tongue = depression_tongue.makeFillet(
#						depression_tongue_fillet, 
#						depression_tongue_edgeZ)

depression_tool = depression_tab.fuse(depression_tongue)
depression_tool = depression_tool.removeSplitter()

basic_tab = tab.cut(depression_tool)
basic_tab = basic_tab.fuse(tongue)
basic_tab = basic_tab.removeSplitter()

# Edges correct
#print("Basic tab edges = " + str(len(basic_tab.Edges)))
#basic_tab_edgeZ_idx = [23, 27] + [69, 75] 
#basic_tab_edgeZ = [basic_tab.Edges[i] for i in basic_tab_edgeZ_idx]
#basic_tab_fillet = 0.1
#basic_tab = basic_tab.makeFillet(basic_tab_fillet, basic_tab_edgeZ)

#%% Sample tab holes
window_hole_r = 1.00
window_hole_H = 3
window_hole_placement = Base.Vector(-tabL/2+5.0,0,-1.5)
window_hole = Part.makeCylinder(window_hole_r, window_hole_H,
								window_hole_placement)

screw_hole_r = 0.75
screw_hole_H = 3.0
screw_hole_cc = 5.0
screw_hole_center1 = Base.Vector(tabL/2-5.0, screw_hole_cc/2, -1.5)
screw_hole_center2 = Base.Vector(tabL/2-5.0, -screw_hole_cc/2, -1.5)
screw_hole1 = Part.makeCylinder(screw_hole_r, screw_hole_H,
								screw_hole_center1)
screw_hole2 = Part.makeCylinder(screw_hole_r, screw_hole_H,
								screw_hole_center2)

tongue_hole_r = 1.25/2
tongue_hole_H = 3
#Verify this
tongue_hole_center = Base.Vector((tabL/2+tongueL)-1.75, 0, -1.5)
tongue_hole = Part.makeCylinder(tongue_hole_r, tongue_hole_H,
								tongue_hole_center)

tab_holes = basic_tab.cut(window_hole).cut(screw_hole1).cut(screw_hole2)
tab_holes = tab_holes.cut(tongue_hole)


full_tab = tab_holes

#Part.show(tab, "tab_box")
#Part.show(tongue, "tongue_box")
#Part.show(depression_tool, "depression_box")
#Part.show(window_cyl, "window hole")
Part.show(full_tab, "full_tab")
