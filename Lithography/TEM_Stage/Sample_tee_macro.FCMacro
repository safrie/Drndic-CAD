import FreeCAD
from FreeCAD import Base

# Location of sample tab and screw holes (NEED TO BE UPDATED IF SAMPLE TAB VALUES CHANGE)
tabL = 17.45
tabW = 11.75
tabH = 0.8
tabPoint = Base.Vector(-tabL/2, -tabW/2, -tabH/2)
tab_screw_hole_cc = 5.0
tab_screw_hole_center1 = Base.Vector(tabL/2-5.0, tab_screw_hole_cc/2, -1.5)
tab_screw_hole_center2 = Base.Vector(tabL/2-5.0, -tab_screw_hole_cc/2, -1.5)

# Basic sample tee shape
teeL = 10.00
teeH = 0.125
crossW = 10.65
crossL = 3.65
legL = teeL - crossL
legW = 2.40
windowOR = 3.00/2
windowIR = 2.15/2
screw_holeR = 1.85/2

crossPoint = Base.Vector(tabL/2-6.75, -crossW/2, tabH/2)
cross = Part.makeBox(crossL, crossW, teeH, crossPoint)

legPoint = Base.Vector(tabL/2-6.75-legL, -legW/2, tabH/2)
leg = Part.makeBox(legL, legW, teeH, legPoint)

windowPoint = Base.Vector(-tabL/2+5.0, 0, tabH/2)
window = Part.makeCylinder(windowOR, teeH, windowPoint)

basic_tee = cross.fuse(leg).fuse(window).removeSplitter()

# Add holes
window_hole = Part.makeCylinder(windowIR, 5, windowPoint)
screw_hole1 = Part.makeCylinder(screw_holeR, 3, tab_screw_hole_center1)
screw_hole2 = Part.makeCylinder(screw_holeR, 3, tab_screw_hole_center2)
tee_cutoutL = 1.0 + screw_holeR
tee_cutoutW = 1.6
tee_cutoutH = teeH
tee_cutoutPoint = Base.Vector(tabL/2-5.0-2*screw_holeR, -tab_screw_hole_cc/2-tee_cutoutW/2, tabH/2)
tee_cutout = Part.makeBox(tee_cutoutL, tee_cutoutW, tee_cutoutH, tee_cutoutPoint)

full_tee = basic_tee.cut(window_hole).cut(screw_hole1).cut(screw_hole2).cut(tee_cutout)



#full_tee = basic_tee
Part.show(full_tee, "full tee")
